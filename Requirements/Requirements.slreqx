# Requirements
For the assignment due 2/12/26

## RFP: Main RFP Requirements (Container)
2025-2026_UG_Team_Navy-RFP.pdf
Requirements V2.xlsx

### 3.1: General Design (Container)

#### 3.1.a: Configuration (Functional)
The aircraft may include any combination of survivability, vulnerability and effectiveness features to maximize its cost-effective capability.

#### 3.1.b: Propulsion System (Container)

##### 3.1.b.a: Number of Engines (Functional)
The aircraft may be a single or multi-engine design.

##### 3.1.b.b: Engine TRL (Functional)
The engine(s) must be an existing production design to minimize development cost.

#### 3.1.c: Materials (Container)

##### 3.1.c.a: Maratime Environment (Functional)
Materials shall be suitable for a 25-year service life in a maritime environment (moisture intrusion, salt spray, etc.).

##### 3.1.c.b: Production (Functional)
Materials must be currently available in production quantities to minimize development risk.

#### 3.1.d: Subsytem TRL (Functional)
All subsystems technologies (including avionics and mission systems) shall currently be at technology readiness level (TRL) 6 or higher.

#### 3.1.e: Ordnance Carriage (Functional)
External carriage of ordnance is acceptable.
Internal carriage of weapons is desirable for reduced radar cross section.

### 3.2: Carrier Sutabiity (Functional)

#### 3.2.a: Carrier Classes (Functional)
The aircraft shall be operable from CVN-68 and CVN-78 class aircraft carriers.

#### 3.2.b: Operational Impact (Functional)
The addition of the aircraft to the existing fleet should have minimal impact on operations for the carrier air wing. Considerations include, but are not limited to, compatibility with existing shipboard equipment, and time or crew support required for launch.

#### 3.2.1: Launch Performance - CMEA (Functional)
Catapult minimum end airspeed
a. Defined as the airspeed required at the end of the catapult stroke to support the aircraft under the conditions of altitude loss, lift limit, pitch rate limit, and longitudinal acceleration specified for catapulting.
b. Catapult minimum end airspeed shall be the highest of the following:
i. An end speed which results in the CG position of the aircraft sinking no more than 10 feet from its position at the end of the power stroke, with a deck run not to exceed 32 feet (distance from the end of the power stroke to round-down), with cockpit control position held either fixed or free or controls active.
ii. The speed represented by 90% of the maximum lift coefficient, power off, out of ground effect.
iii. The minimum airspeed at which the aircraft has a longitudinal acceleration of 0.065g (2.0913 ft/sec2) at zero flight path angle.
iv. If multi-engine, the minimum aircraft control speed with one engine inoperative

#### 3.2.2: Recovery Performance - Arrestment Speed (Functional)
a) Arrestment engaging speed (horizontal aircraft velocity relative to the ship at touchdown) shall be assumed to be 5% greater than approach speed.
b) Approach airspeed shall be greater than 10% above stall speed, but less than 145 knots.
c) Arrestment landing weight shall include sufficient fuel for 20 minutes loiter at 10,000 ft and two landing attempts, 25% maximum fuel weight, and 50% store weight.

### 3.3: Payload Requirements (Container)

#### 3.3.1: Air to Air Combat (Functional)
a) Avionics/sensors weight shall be 2,500 lb. (internal to airframe)
b) Ordnance load shall be:
a. AIM-120C: QTY 6
b. AIM-9X: QTY 2

#### 3.3.2: Strike (Functional)
a) Avionics/sensors weight shall be 2,500 lb. (internal to airframe)
b) Ordnance load shall be:
a. MK-83 JDAM: QTY 4
b. AIM-9X: QTY 2

### 3.4: Mission Requirements (Container)

#### 3.4.1: Air to Air Combat (Container)

##### 3.4.1.a: Combat Radius (Functional)
A 700 nm. minimum combat radius is required. A 1,000 nm. combat radius is desirable.

##### 3.4.1.b: Combat Time (Functional)
Combat shall consist of a minimum of 2 minutes at maximum thrust at best turning speed (speed for highest rate of turn) at 10,000 ft. A combat time of 5 minutes at maximum thrust is desirable.

##### 3.4.1.c: Carrying Ordnance (Functional)
Ordinance shall be carried for the entire mission (including arrestment).

##### 3.4.1.d: Turn Rate (Functional)
The aircraft shall have an 8.0 deg/sec minimum sustained turn rate at 20,000 ft at the mid mission fuel weight. A 10.0 deg/sec turn rate is desirable.

##### 3.4.1.e: Dash Speed (Functional)
A Mach 1.6 dash speed at 30,000 ft. is required. Mach 2.0 dash speed is desired.

#### 3.4.2: Strike (Container)

##### 3.4.2.a: Combat Radius (Functional)
A 700 nm. minimum combat radius is required. A 1,000 nm. combat radius is desirable.

##### 3.4.2.b: Sea Level Dash (Functional)
Mid mission combat shall consist of 50 nm sea level dashes (ingress and egress) at intermediate thrust (maximum non-afterburning)

##### 3.4.2.c: Sea Level Dash Speed (Functional)
Sea level dash speed shall be Mach .85 or greater (intermediate thrust). Mach .90 is desirable.

##### 3.4.2.d: Carrying Ordnance (Functional)
Ordinance shall be carried for the entire mission (including arrestment).

### 3.5: Point Performance (CVN-68) (Container)

#### 3.5.a: Design Load Factor (Functional)
The design vertical load factor (Nz) shall be greater than 7g at mid mission weight. 8.0g is desirable.

#### 3.5.b: External Store Capability (Functional)
Aircraft external store carriage capability (ordnance, tanks, or pods) shall not be less than 10,000 lb in total or less than 3,000 lb for any single store.

#### 3.5.c: Wind Over Deck (Functional)
Launch requirements must be achievable with a Wind Over Deck (WOD) no greater than zero (i.e., no headwind) and using the C-13-2 catapult (see performance chart provided in Section 5)

#### 3.5.d: Arresting Gear (Functional)
Recovery requirements must be achievable with a WOD not greater than 15 knots and using the Mark 7 Mod 3 arresting gear (see performance chart provided in Section 5).

#### 3.5.e: Launch SEROC (Functional)
If multi-engine, launch single-engine rate of climb (SEROC) not less than 200 ft/min.

#### 3.5.f: Approach SEROC (Functional)
If multi-engine, approach SEROC not less than 500 ft/min.

#### 3.5.g: Unfolded Wingspan (Functional)
Unfolded wingspan shall not exceed 60 feet.

#### 3.5.h: Folded Wingspan (Functional)
Folded wingspan shall not exceed 35 feet.

#### 3.5.i: Overall Aircraft Length (Functional)
Overall aircraft length shall not exceed 50 feet (jet blast deflector clearance).

#### 3.5.j: Overall Aircraft Height (Functional)
Overall aircraft height shall not exceed 18.5 feet (aft hangar bay height).

#### 3.5.k: Spot Factor (Functional)
Spot factor should be minimized by minimizing total planform area for aircraft in stowed configuration (e.g., wings folded).

#### 3.5.l: MTOW Limit (Functional)
Maximum take-off gross weight shall not be greater than 90,000 lb (elevator deck strength limits and support equipment capability).
